module ietf-bgp-ls {
  yang-version 1.1;
  namespace "urn:ietf:params:xml:ns:yang:ietf-bgp-ls";
  prefix bgp-ls;

  import ietf-inet-types {
    prefix inet;
    reference
      "RFC 9911: Common YANG Data Types.";
  }
  import ietf-yang-types {
    prefix yang;
    reference
      "RFC 9911: Common YANG Data Types.";
  }
  import ietf-routing {
    prefix rt;
    reference
      "RFC 8349, A YANG Data Model for Routing Management
       (NMDA Version).";
  }
  import ietf-routing-types {
    prefix ietf-rt-t;
    reference
      "RFC 8294: Common YANG Data Types for the Routing Area.";
  }
  import ietf-isis {
    prefix ietf-isis-t;
    reference
      "RFC 9130: YANG Data Model for IS-IS Protocol.";
  }
  import ietf-ospf {
    prefix ietf-ospf-t;
    reference
      "RFC 9129: YANG Data Model for the OSPF Protocol.";
  }
  import ietf-bgp {
    prefix bgp;
    reference
      "I-D.ietf-idr-bgp-model: BGP YANG Model for Service Provider
                               Networks.";
  }
  import iana-bgp-afi-safi-types {
    prefix bast;
    reference
      "I-D.ietf-idr-bgp-model: BGP YANG Model for Service Provider
                               Networks.";
  }
  import ietf-bgp-types {
    prefix ibt;
    reference
      "I-D.ietf-idr-bgp-model: BGP YANG Model for Service Provider
                               Networks.";
  }
  import ietf-bgp-lsdb {
    prefix bgp-lsdb;
    reference
      "RFC XXXX: A YANG model for BGP-LS, BGP-LS-VPN,
                 and BGP-LS-SPF.";
  }
  import ietf-bgp-ls-topo-types {
    prefix bgp-ls-topo-t;
    reference
      "RFC XXXX: A YANG model for BGP-LS, BGP-LS-VPN,
                 and BGP-LS-SPF.";
  }

  organization
    "IETF LSVR Working Group";
  contact
    "WG Web:   <https://datatracker.ietf.org/wg/lsvr>
     WG List:  <lsvr@ietf.org>

     Authors: Mahesh Jethanandani (mjethanandani at gmail.com),
              Keyur Patel (keyur at arrcus.com),
              Aravind Babu MahendraBabu (aramahen at cisco.com)";

  description
    "This module contains contains management
     information for BGP-LS database.

     Copyright (c) 2023 IETF Trust and the persons identified as
     authors of the code. All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  revision YYYY-MM-DD {
    description
      "Initial Version";
    reference
      "RFC XXXX, BGP Model for Link State Distribution.";
  }

  // Identities.
  identity bgp-ls {
    base bast:afi-safi-type;
    description
      "BGP Link-State.";
    reference
      "RFC 9552: Distribution of Link-State and Traffic Engineering
       Information Using BGP.";
  }

  identity bgp-ls-vpn {
    base bast:afi-safi-type;
    description
      "BGP Link-State VPN.";
    reference
      "RFC 9552: Distribution of Link-State and Traffic Engineering
       Information Using BGP.";
  }

  identity bgp-ls-spf {
    base bast:afi-safi-type;
    description
      "BGP Link-State Shortest Path First (BGP-LS-SPF).";
    reference
      "RFC 9815: BGP Link-State SPF Routing.";
  }

  identity attribute-type {
    description
      "Base identity for BGP-LS Attribute type.";
  }

  identity multi-topology-identifier {
    base attribute-type;
    description
      "Multi Topology Identifier TLV.";
    reference
      "RFC 9552: Distribution of Link-State and Traffic Engineering
       Information Using BGP.";
  }

  identity node-flag-bits {
    base attribute-type;
    description
      "The Node Flag Bits TLV.";
    reference
        "RFC 9552: Distribution of Link-State and Traffic
         Engineering Information Using BGP.";
  }

  identity opaque-node-attribute {
    base attribute-type;
    description
      "The Opaque Node Attribute TLV.";
    reference
      "RFC 9552: Distribution of Link-State and Traffic Engineering
       Information Using BGP.";
  }

  identity node-name {
    base attribute-type;
    description
      "The Node Name TLV.";
    reference
      "RFC 9552: Distribution of Link-State and Traffic Engineering
       Information Using BGP.";
  }

  identity isis-area-identifier {
    base attribute-type;
    description
      "IS-IS Area Identifier.";
    reference
      "RFC 9552: Distribution of Link-State and Traffic Engineering
       Information Using BGP."; 
  }

  identity ipv4-route-id-of-local-node {
    base attribute-type;
    description
      "IPv4 Router-ID of Local Node.";
    reference
      "RFC 9552: Distribution of Link-State and Traffic Engineering
       Information Using BGP."; 
  }

  identity ipv6-router-id-of-local-node {
    base attribute-type;
    description
      "IPv6 Router-ID of Local Node.";
    reference
      "RFC 9552: Distribution of Link-State and Traffic Engineering
       Information Using BGP."; 
  }

  // Typedefs
  typedef spf-algorithm-type {
    type enumeration {
      enum normal {
        description
          "Normal Shortest Path First (SPF) algorithm based on link 
           metric. This is the standard shortest path algorithm as 
           computed by the IGP protocol. Consistent with the
           deployed practice for link-state protocols, Algorithm 0
	   permits any node to overwrite the SPF path with a
	   different path based on its local policy.";
      }
      enum strict {
        description
          "Strict Shortest Path First (SPF) algorithm based on link
           metric. The algorithm is identical to Algorithm 0 but
           Algorithm 1 requires that all nodes along the path will
           honor the SPF routing decision. Local policy at the node
           claiming support for Algorithm 1 MUST NOT alter the SPF
           paths computed by Algorithm 1";
      }
      enum unknown {
        description
          "Unknown Algorithm";
      }
    }
    description
      "SPF algorithm type.";
  }
      
  // Groupings
  grouping bgp-neighbor-ls-common {
    description
      "Grouping for neighbor configuration for Link-State.";
    
      leaf metric {
        type uint32;
        default 10;
        description 
          "Metric associated with the corresponding link to 
           be used in the SPF graph computation.";
      }

      leaf status {
        type enumeration {
          enum reachable {
            description
              "The link is reachable in the current SPF topology.";
          }
          enum unreachable {
            description
              "The link is unreachable in the current SPF
               topology.";
          }
        }
        default reachable;
        description 
          "Sets SPF-Status of the corresponding LS Link NLRI.";

      }
  }

  grouping bgp-mp-ls {
    description
      "Grouping for BGP-LS paramters.";

    container link-state {
      when "derived-from-or-self(../../bgp:afi-safi/bgp:name, " +
           "'bgp-ls')" {
	      description
	        "Include this container for BGP Linkstate specific
           configuration";
      }
      presence
	      "This container is for BGP Linkstate specific
              congfiguration.";
      
      description
        "Information related to Link-State configuration and
         management.";

      uses bgp:mp-all-afi-safi-common;

      leaf max-rate {
        type uint32;
        units per-second;
        default 200;
        description
          "Maximum rate at which Link-State NLRIs will be
           advertised or withdrawn from neighbors.";
        reference
          "RFC 9552: Distribution of Link-State and Traffic
           Engineering Information Using BGP.";
      }

      leaf max-number {
        type uint32;
        description
          "Maximim number of Link-State NLRIs stored in a router's
           RIB.";
        reference
          "RFC 9552: Distribution of Link-State and Traffic
           Engineering Information Using BGP.";
      }
    }
  }

  grouping bgp-mp-ls-spf {
    description
      "Grouping for BGP-LS-SPF parameters.";
    
    container link-state-spf {
      when "derived-from-or-self (../../bgp:afi-safi/bgp:name, " +
                                 "'bgp-ls-spf')" {
	description
	  "Include this container for BGP Link-State SPF specific
           configuration";
      }
      description "BGP Linkstate-SPF configuration options";

      uses bgp:mp-all-afi-safi-common;
    }
  }

  grouping bgp-ls-rib-route-key {
    description
      "Grouping for the key that identifies a Link-State NLRI in
       the BGP RIB.";

    leaf nlri {
      type yang:hex-string;
      description
        "The Link-State NLRI, encoded as specified in RFC 9552,
         starting with the NLRI Type field. For BGP-LS-VPN, the
         NLRI includes the Route Distinguisher.

         The encoded NLRI is used as the key because RFC 9552
         identifies an NLRI by a binary comparison of its encoding,
         including any sub-TLVs unknown to the implementation. The
         decoded descriptors of the NLRI are provided as non-key
         leaves.";
      reference
        "RFC 9552: Distribution of Link-State and Traffic
         Engineering Information Using BGP, Section 5.2.";
    }
  }

  grouping bgp-ls-rib-node-descriptors {
    description
      "Decoded Node Descriptor sub-TLVs of a Link-State NLRI.
       Leaves are present only when the corresponding sub-TLV is
       present in the NLRI.";
    reference
      "RFC 9552: Distribution of Link-State and Traffic
       Engineering Information Using BGP, Section 5.2.1.4.";

    leaf as {
      type inet:as-number;
      description
        "Autonomous System (AS) number associated with the BGP
         process originating the link-state information.";
    }

    leaf bgp-ls-identifier {
      type uint32;
      status deprecated;
      description
        "BGP-LS Identifier. Deprecated by RFC 9552, and present
         only for compatibility with RFC 7752 implementations.";
    }

    leaf area-id {
      type ietf-ospf-t:area-id-type;
      description
        "OSPF Area ID to which the information advertised in the
         NLRI belongs.";
    }

    choice igp-router-id {
      description
        "Decoded IGP Router-ID. The form of the Router-ID depends
         on the protocol from which the NLRI was learned.";

      case isis {
        leaf system-id {
          type ietf-isis-t:system-id;
          description
            "IS-IS System ID of the node, or of the Designated
             Intermediate System (DIS) for a pseudonode.";
        }

        leaf psn-id {
          type uint8 {
            range "1..255";
          }
          description
            "Pseudonode (PSN) identifier. Present only for an IS-IS
             pseudonode.";
        }
      }

      case ospf {
        leaf router-id {
          type ietf-rt-t:router-id;
          description
            "OSPF Router ID of the node, or of the Designated
             Router (DR) for a pseudonode.";
        }

        leaf dr-identifier {
          type inet:ipv4-address;
          description
            "IPv4 address of the DR's interface to the LAN.
             Present only for an OSPFv2 pseudonode.";
        }

        leaf dr-interface-id {
          type uint32;
          description
            "Interface identifier of the DR's interface to the LAN.
             Present only for an OSPFv3 pseudonode.";
        }
      }

      case direct-or-static {
        leaf router-address {
          type inet:ip-address;
          description
            "IPv4 or IPv6 address configured on the node, used as
             the Router-ID for 'Direct' or 'Static configuration'.";
        }
      }
    }

    leaf bgp-router-id {
      type yang:dotted-quad;
      description
        "BGP Router-ID of the node, for NLRIs whose protocol is
         BGP.";
      reference
        "RFC 9086: Border Gateway Protocol - Link State (BGP-LS)
         Extensions for Segment Routing BGP Egress Peer
         Engineering, Section 4.1.";
    }

    leaf member-as {
      type inet:as-number;
      description
        "AS number of the BGP confederation member, for NLRIs
         whose protocol is BGP.";
      reference
        "RFC 9086: Border Gateway Protocol - Link State (BGP-LS)
         Extensions for Segment Routing BGP Egress Peer
         Engineering, Section 4.1.";
    }
  }

  grouping bgp-ls-rib-nlri-descriptors {
    description
      "Decoded descriptors of a Link-State NLRI. These are derived
       from the 'nlri' key of the route and are provided for
       readability.";
    reference
      "RFC 9552: Distribution of Link-State and Traffic
       Engineering Information Using BGP, Section 5.2.";

    leaf route-distinguisher {
      when "derived-from-or-self(ancestor::bgp:afi-safi/bgp:name, "
         + "'bgp-ls:bgp-ls-vpn')" {
        description
          "Include this leaf only for BGP-LS-VPN.";
      }
      type ietf-rt-t:route-distinguisher;
      description
        "Route Distinguisher of a BGP-LS-VPN NLRI.";
    }

    container local-node-descriptors {
      when "../nlri-type = 'node' or ../nlri-type = 'link' or "
         + "../nlri-type = 'ipv4-prefix' or "
         + "../nlri-type = 'ipv6-prefix'" {
        description
          "Include this container for Node, Link, and Prefix
           NLRIs.";
      }
      description
        "Descriptors of the node anchoring the local end of the
         link, or the node itself for a Node NLRI.";
      reference
        "RFC 9552: Distribution of Link-State and Traffic
         Engineering Information Using BGP, Section 5.2.1.2.";
      uses bgp-ls-rib-node-descriptors;
    }

    container remote-node-descriptors {
      when "../nlri-type = 'link'" {
        description
          "Include this container only for Link NLRIs.";
      }
      description
        "Descriptors of the node anchoring the remote end of the
         link.";
      reference
        "RFC 9552: Distribution of Link-State and Traffic
         Engineering Information Using BGP, Section 5.2.1.3.";
      uses bgp-ls-rib-node-descriptors;
    }

    container link-descriptors {
      when "../nlri-type = 'link'" {
        description
          "Include this container only for Link NLRIs.";
      }
      description
        "Descriptors that uniquely identify a link among multiple
         parallel links between a pair of anchor nodes. Leaves are
         present only when the corresponding TLV is present in the
         NLRI.";
      reference
        "RFC 9552: Distribution of Link-State and Traffic
         Engineering Information Using BGP, Section 5.2.2.";

      leaf link-local-identifier {
        type uint32;
        description
          "Link Local Identifier.";
      }

      leaf link-remote-identifier {
        type uint32;
        description
          "Link Remote Identifier.";
      }

      leaf ipv4-interface-address {
        type inet:ipv4-address;
        description
          "IPv4 interface address.";
      }

      leaf ipv4-neighbor-address {
        type inet:ipv4-address;
        description
          "IPv4 neighbor address.";
      }

      leaf ipv6-interface-address {
        type inet:ipv6-address;
        description
          "IPv6 interface address.";
      }

      leaf ipv6-neighbor-address {
        type inet:ipv6-address;
        description
          "IPv6 neighbor address.";
      }

      leaf multi-topology-id {
        type uint16 {
          range "0..4095";
        }
        description
          "Multi-Topology Identifier of the topology in which the
           link is reachable.";
        reference
          "RFC 9552: Distribution of Link-State and Traffic
           Engineering Information Using BGP, Section 5.2.2.1.";
      }
    }

    container prefix-descriptors {
      when "../nlri-type = 'ipv4-prefix' or "
         + "../nlri-type = 'ipv6-prefix'" {
        description
          "Include this container only for IPv4 and IPv6 Prefix
           NLRIs.";
      }
      description
        "Descriptors that uniquely identify a prefix originated by
         a node. Leaves are present only when the corresponding TLV
         is present in the NLRI.";
      reference
        "RFC 9552: Distribution of Link-State and Traffic
         Engineering Information Using BGP, Section 5.2.3.";

      leaf multi-topology-id {
        type uint16 {
          range "0..4095";
        }
        description
          "Multi-Topology Identifier of the topology in which the
           prefix is reachable.";
        reference
          "RFC 9552: Distribution of Link-State and Traffic
           Engineering Information Using BGP, Section 5.2.2.1.";
      }

      leaf ospf-route-type {
        type bgp-ls-topo-t:ospf-route-type;
        description
          "OSPF route type of the prefix.";
        reference
          "RFC 9552: Distribution of Link-State and Traffic
           Engineering Information Using BGP, Section 5.2.3.1.";
      }

      leaf ip-reachability-information {
        type inet:ip-prefix;
        description
          "The IPv4 or IPv6 prefix originally advertised in the IGP
           topology.";
        reference
          "RFC 9552: Distribution of Link-State and Traffic
           Engineering Information Using BGP, Section 5.2.3.2.";
      }
    }
  }

  grouping bgp-ls-rib-route-state {
    description
      "Grouping for the state associated with a Link-State NLRI
       in the BGP RIB.";

    leaf nlri-type {
      type bgp-ls-topo-t:nlri-type;
      description
        "The type of Link-State NLRI.";
      reference
        "RFC 9552: Distribution of Link-State and Traffic
         Engineering Information Using BGP, Section 5.2.";
    }

    leaf protocol-id {
      type bgp-ls-topo-t:protocol;
      description
        "The protocol from which the Link-State information
         carried in the NLRI was learned.";
      reference
        "RFC 9552: Distribution of Link-State and Traffic
         Engineering Information Using BGP, Section 5.2.";
    }

    leaf identifier {
      type uint64;
      description
        "Instance identifier identifying the IGP routing domain
         where the NLRI belongs.";
      reference
        "RFC 9552: Distribution of Link-State and Traffic
         Engineering Information Using BGP, Section 5.2.";
    }

    uses bgp-ls-rib-nlri-descriptors;

    leaf ls-attribute {
      type yang:hex-string;
      description
        "The BGP-LS Attribute associated with the NLRI, encoded as
         a set of TLVs. The decoded contents of the attribute are
         available in the Link-State database.";
      reference
        "RFC 9552: Distribution of Link-State and Traffic
         Engineering Information Using BGP, Section 5.3.";
    }

    leaf sequence-number {
      when "derived-from-or-self(ancestor::bgp:afi-safi/bgp:name, "
         + "'bgp-ls:bgp-ls-spf')" {
        description
          "Include this leaf only for BGP-LS-SPF.";
      }
      type uint64;
      description
        "The sequence number carried in the BGP-LS-SPF Sequence
         Number TLV. The TLV is mandatory for BGP-LS-SPF
         NLRIs, and an NLRI received without it is treated as
         withdrawn.  This leaf is therefore present for every
         BGP-LS-SPF route, except one received without a BGP-LS
         Attribute, which is preserved and propagated but not used
         in the SPF calculation.";
      reference
        "RFC 9815: BGP Link-State SPF Routing, Sections 5.2.4,
         6.1, and 7.1.";
    }

    uses bgp:bgp-common-route-annotations-state;
    uses bgp:bgp-unknown-attr-top;
    uses bgp:rib-ext-route-annotations;
  }

  grouping bgp-ls-adj-rib-common {
    description
      "Common structural grouping for each Link-State Adj-RIB
       table.";

    container routes {
      config false;
      description
        "Enclosing container for the list of Link-State routes in
         the table.";

      list route {
        key "nlri path-id";
        description
          "List of Link-State routes in the table, keyed by the
           NLRI and path-id, to distinguish multiple routes
           received from a neighbor for the same NLRI.";

        uses bgp-ls-rib-route-key;
        uses bgp:bgp-adj-rib-attr-state;
        uses bgp:bgp-adj-rib-common-attr-refs;
        uses bgp-ls-rib-route-state;
      }
    }
  }

  grouping bgp-ls-adj-rib-in-post {
    description
      "Structural grouping for the Link-State Adj-RIB-In
       post-policy table.";

    uses bgp-ls-adj-rib-common {
      augment "routes/route" {
        description
          "Add best-path annotation to Adj-RIB-In post-policy
           routes.";
        uses bgp:bgp-adj-rib-in-post-route-annotations-state;
      }
    }
  }

  grouping bgp-ls-rib {
    description
      "Grouping for the BGP-LS, BGP-LS-VPN, and BGP-LS-SPF
       routing tables.";

    container link-state {
      when "derived-from-or-self(../bgp:name, 'bgp-ls:bgp-ls') or "
         + "derived-from-or-self(../bgp:name, 'bgp-ls:bgp-ls-vpn') or "
         + "derived-from-or-self(../bgp:name, 'bgp-ls:bgp-ls-spf')" {
        description
          "Include this container for the BGP-LS, BGP-LS-VPN, and
           BGP-LS-SPF RIBs.";
      }
      description
        "Routing tables for Link-State -- active when the afi-safi
         name is bgp-ls, bgp-ls-vpn, or bgp-ls-spf.";
      reference
        "RFC 9552: Distribution of Link-State and Traffic
         Engineering Information Using BGP, Section 5.2.
         RFC 9815: BGP Link-State SPF Routing.";

      container loc-rib {
        config false;
        description
          "Container for the Link-State BGP Loc-RIB data.";

        container routes {
          description
            "Enclosing container for the list of Link-State routes
             in the routing table.";

          list route {
            key "nlri origin path-id";
            description
              "List of Link-State routes in the table, keyed by the
               NLRI, the route origin, and path-id. The route origin
               can be either the neighbor address from which the
               route was learned, or the source protocol that
               injected the route. The path-id distinguishes routes
               for the same NLRI received from a neighbor (e.g., if
               add-paths is enabled).";

            uses bgp-ls-rib-route-key;
            uses bgp:bgp-loc-rib-common-keys;
            uses bgp:bgp-loc-rib-common-attr-refs;
            uses bgp-ls-rib-route-state;
          }
        }
      }

      container neighbors {
        config false;
        description
          "Enclosing container for neighbor list.";

        list neighbor {
          key "neighbor-address";
          description
            "List of neighbors (peers) of the local BGP speaker.";

          leaf neighbor-address {
            type inet:ip-address;
            description
              "IP address of the BGP neighbor or peer.";
          }

          container adj-rib-in-pre {
            description
              "Per-neighbor table containing the Link-State routes
               received from the neighbor before any local input
               policy rules or filters have been applied.";
            uses bgp-ls-adj-rib-common;
            uses bgp:clear-routes {
              description
                "Clears the adj-rib-in state for the containing
                 neighbor.";
            }
          }

          container adj-rib-in-post {
            description
              "Per-neighbor table containing the Link-State routes
               received from the neighbor that are eligible for
               best-path selection after local input policy rules
               have been applied.";
            uses bgp-ls-adj-rib-in-post;
            uses bgp:clear-routes {
              description
                "Clears the adj-rib-in state for the containing
                 neighbor.";
            }
          }

          container adj-rib-out-pre {
            description
              "Per-neighbor table containing Link-State routes
               eligible for sending (advertising) to the neighbor
               before output policy rules have been applied.";
            uses bgp-ls-adj-rib-common;
            uses bgp:clear-routes {
              description
                "Clears the adj-rib-out state for the containing
                 neighbor.";
            }
          }

          container adj-rib-out-post {
            description
              "Per-neighbor table containing Link-State routes
               eligible for sending (advertising) to the neighbor
               after output policy rules have been applied.";
            uses bgp-ls-adj-rib-common;
            uses bgp:clear-routes {
              description
                "Clears the adj-rib-out state for the containing
                 neighbor.";
            }
          }
        }
      }
    }
  }

  augment "/rt:routing/rt:control-plane-protocols" +
          "/rt:control-plane-protocol/bgp:bgp/bgp:global" +
          "/bgp:afi-safis/bgp:afi-safi" {
    description
      "Augmentation of the BGP model to add BGL-LS.";
    uses bgp-mp-ls;
    uses bgp-mp-ls-spf;
  }

  augment "/rt:routing/rt:control-plane-protocols" +
          "/rt:control-plane-protocol/bgp:bgp/bgp:global" +
          "/bgp:afi-safis/bgp:afi-safi/link-state" {
    description
      "Augmentation of BGL-LS to add dB.";
    uses bgp-lsdb:lsdb-top;
  }

  augment "/rt:routing/rt:control-plane-protocols" +
          "/rt:control-plane-protocol/bgp:bgp/bgp:global" +
          "/bgp:afi-safis/bgp:afi-safi/link-state-spf" {
    description
      "Augmentation of BGL-LS-SPF.";

    leaf instance-identifier {
      type uint64;
      default 0;
      description 
        "Instance Identifier to be used for all Link-State NLRI 
         advertisements originated locally";
    }

    leaf algorithm-type {
      type spf-algorithm-type;
      default normal;
      description 
        "SPF Algorithm type associated with Link-State AFI SAFI";
    }

    leaf node-status {
      type enumeration {
        enum reachable {
          description
            "The local node is reachable in the current SPF
	     topology.";
        }
        enum unreachable {
          description
            "The local node is unreachable in the current SPF
	     topology.";
        }
        enum no-transit-support {
          description
            "The local node is reachable but does not support
	     forwarding of transit traffic.";
        }
      }
      default reachable;
      description 
        "Sets SPF-Status of the local node.";
    }

    container log {
      config false;
      description
        "This container lists the SPF computation events.";
    
      list event {
        key id;
        description
          "List of computation events - implemented as a
           wrapping buffer.";

        leaf id {
          type uint32;
          description
            "Event identifier.";
        }

        leaf type {
          type enumeration {
            enum full {
              description "Full SPF computation.";
            }
            enum route-only {
              description
                "Route reachability only SPF computation";
            }
          }
          description "Type of SPF computation performed.";
        }

        leaf schedule-time {
          type yang:date-and-time;
          description
            "Time when the SPF computation was
             scheduled.";
        }

        leaf delay {
          type uint64;
          description
            "Delay in micro-seconds applied for this SPF event.";
        }

        leaf start-time {
          type yang:date-and-time;
          description
            "Time when the SPF computation started.";
        }

        leaf end-time {
          type yang:date-and-time;
          description
            "Time when the SPF computation ended.";
        }

        leaf duration {
          type uint64;
          description
            "Time taken in micro-seconds to execute the SPF
	     computations.";
        }

        leaf node-count {
          type uint64;
          description
            "Number of nodes involved in the SPF computations.";
        }

        leaf prefix-count {
          type uint64;
          description
            "Number of prefixes involved in the SPF computations.";
        }

        leaf route-download-count {
          type uint64;
          description
            "Number of routes updated in the SPF computations.";
        }

        list lsp-trigger {
          key "id";
          description
            "This list includes the LSPs that triggered the
             SPF computation.";

          leaf id {
            type uint32;
            description
              "Trigger identifier.";
          }

          leaf nlri-prefix {
            type string;
            description
              "Prefix of the NLRI triggering SPF computation.";
          }

          leaf nlri-sequence {
            type uint32;
            description
              "Sequence number of the NLRI triggering SPF
	       computation.";
          }

          leaf trigger-time {
            type yang:date-and-time;
            description
              "Time when the trigger event was recorded.";
          }
        }
      }
    }
    uses bgp-lsdb:lsdb-top;
  }

  augment "/rt:routing/rt:control-plane-protocols" +
          "/rt:control-plane-protocol/bgp:bgp/bgp:neighbors" +
          "/bgp:neighbor/bgp:afi-safis/bgp:afi-safi" {
    description
      "Augmentation of the BGP model to add BGL-LS.";
    uses bgp-mp-ls;
    uses bgp-mp-ls-spf;
  }

  augment "/rt:routing/rt:control-plane-protocols" +
          "/rt:control-plane-protocol/bgp:bgp/bgp:neighbors" +
          "/bgp:neighbor/bgp:afi-safis/bgp:afi-safi/link-state-spf" {
    description
      "Augmentation of the BGP neighbor to add BGL-LS.";
    uses bgp-neighbor-ls-common;
  }

  /*
  augment "/rt:routing/rt:control-plane-protocols" +
          "/rt:control-plane-protocol/bgp:bgp/bgp:global" +
          "/bgp:afi-safis/bgp:afi-safi/bgp:statistics" {
    when "derived-from-or-self (../bgp:name, 'bgp-ls')" {
      description
        "Include these for BGP Link-State specific statistics.";
    }
    description
      "Augmentation of the global statistics counter to add
       BGP-LS statistics.";

    leaf updates-sent {
      type yang:zero-based-counter32;
      description
        "Total number of Link-State NLRI updates sent.";
      reference
        "RFC 9552: Distribution of Link-State and Traffic
         Engineering Information Using BGP.";
    }

    leaf updates-received {
      type yang:zero-based-counter32;
      description
        "Total number of Link-State NLRI updates received.";
      reference
        "RFC 9552: Distribution of Link-State and Traffic
         Engineering Information Using BGP.";
    }

    leaf local-ls-originated {
      type yang:zero-based-counter32;
      description
        "Total number of locally originated Link-State NLRIs.";
      reference
        "RFC 9552: Distribution of Link-State and Traffic
         Engineering Information Using BGP.";
    }

    action clear {
      if-feature "ibt:clear-statistics";
      description
        "Clear statistics action command.

        Execution of this command should result in all the
        counters to be cleared and set to 0.";

      input {
        leaf clear-at {
          type yang:date-and-time;
          description
            "Time when the clear action needs to be executed.";
        }
      }

      output {
        leaf clear-finished-at {
          type yang:date-and-time;
            description
              "Time when the clear action command completed.";
        }
      }
    }
  }
  augment "/rt:routing/rt:control-plane-protocols" +
          "/rt:control-plane-protocol/bgp:bgp/bgp:global" +
          "/bgp:afi-safis/bgp:afi-safi/bgp:statistics" {
    when "derived-from-or-self (../bgp:name, 'bgp-ls-spf')" {
      description
        "Include these for BGP Link-State SPF specific statistics.";
    }
    description
      "Augmentation of the global statistics counter to add
       BGP-LS-SPF statistics.";

    leaf scheduled {
      type yang:zero-based-counter64;
      description
        "Number of times SPF has been re/scheduled";
    }

    leaf computed {
      type yang:zero-based-counter64;
      description
        "Number of times SPF has been computed";
    }

    leaf maximum-duration {
      type uint64;
      units "microseconds";
      description
        "Maximum duration taken for SPF compuation in
         microseconds.";
    }

    leaf minimum-duration {
      type uint64;
      units "microseconds";
      description
        "Minimum duration taken for SPF compuation in
         microseconds.";
    }

    leaf average-duration {
      type uint64;
      units "microseconds";
      description
        "Average duration taken for SPF compuation in
         microseconds.";
    }

    leaf last-computation-time {
      type yang:date-and-time;
      description
        "Timestamp for last SPF computation for this
         address-family";
    }
  }
  */
  augment "/rt:routing/rt:control-plane-protocols" +
          "/rt:control-plane-protocol/bgp:bgp/bgp:neighbors" +
          "/bgp:neighbor/bgp:statistics" {
    when "derived-from-or-self (../bgp:afi-safis/bgp:afi-safi" +
                               "/bgp:name, 'bgp-ls')" {
      description
        "Include these for BGP Link-State specific statistics.";
    }
    description
      "Augmentation of the BGP per-neighbor statistics to add
       BGP-LS specific counters.";

    leaf updates-sent {
      type yang:zero-based-counter32;
      description
        "Total number of Link-State NLRIs updates sent per
         neighbor.";
      reference
        "RFC 9552: Distribution of Link-State and Traffic
         Engineering Information Using BGP.";
    }

    leaf updates-received {
      type yang:zero-based-counter32;
      description
        "Total number of Link-State NLRIs updates received per
         neighbor.";
      reference
        "RFC 9552: Distribution of Link-State and Traffic
         Engineering Information Using BGP.";
    }

    leaf error-updates-received {
      type yang:zero-based-counter32;
      description
        "Total number of Link-State NLRIs updates received that
         were errored, per neighbor.";
      reference
        "RFC 9552: Distribution of Link-State and Traffic
         Engineering Information Using BGP.";
    }

    leaf computations {
      type yang:zero-based-counter32;
      description
        "Count of number of SPF computations made.";
        reference
          "RFC 9815: BGP Link-State SPF Routing.";
    }

    leaf triggering-events {
      type yang:zero-based-counter32;
      description
        "SPF triggering events.";
        reference
          "RFC 9815: BGP Link-State SPF Routing.";
    }

    action clear {
      if-feature "ibt:clear-statistics";
      description
        "Clear statistics action command.

        Execution of this command should result in all the
        counters to be cleared and set to 0.";

      input {
        leaf clear-at {
          type yang:date-and-time;
          description
            "Time when the clear action needs to be executed.";
        }
      }

      output {
        leaf clear-finished-at {
          type yang:date-and-time;
            description
              "Time when the clear action command completed.";
        }
      }
    }
  }

  augment "/rt:routing/rt:control-plane-protocols" +
          "/rt:control-plane-protocol/bgp:bgp/bgp:peer-groups" +
          "/bgp:peer-group/bgp:afi-safis/bgp:afi-safi" {
    description
      "Augmentation of the BGP peer-group to add BGP-LS and
       BGP-LS-SPF.";

    uses bgp-mp-ls;
    uses bgp-mp-ls-spf;
  }

  augment "/rt:routing/rt:control-plane-protocols" +
          "/rt:control-plane-protocol/bgp:bgp/bgp:peer-groups" +
          "/bgp:peer-group/bgp:afi-safis/bgp:afi-safi/" +
          "link-state-spf" {
    description
      "Augmentation of the BGP peer-groups to add BGL-LS.";
    uses bgp-neighbor-ls-common;
  }

  augment "/rt:routing/rt:control-plane-protocols" +
          "/rt:control-plane-protocol/bgp:bgp/bgp:rib" +
          "/bgp:afi-safis/bgp:afi-safi" {
    description
      "Augmentation of the BGP RIB to add the BGP-LS, BGP-LS-VPN,
       and BGP-LS-SPF routing tables.";
    uses bgp-ls-rib;
  }
}
