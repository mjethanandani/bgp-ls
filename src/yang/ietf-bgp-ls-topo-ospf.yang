submodule ietf-bgp-ls-topo-ospf {
  yang-version 1.1;

  belongs-to ietf-bgp-lsdb {
    prefix "bgp-lsdb";
  }

  import ietf-inet-types { 
    prefix inet;
    reference
      "RFC 9911: Common YANG Data Types.";
  }

  import ietf-bgp-ls-topo-types {
    prefix bgp-ls-topo-t;
    reference
      "RFC XXXX: BGP Model for Link State Distribution.";
  }

  import ietf-routing-types { 
    prefix ietf-rt-t;
    reference
      "RFC 8294: Common YANG Data Types for the Routing Area.";
  }

  import ietf-ospf { 
    prefix ietf-ospf-t;
    reference
      "RFC 9129: YANG Data Model for the OSPF Protocol.";
  }

  organization
    "IETF LSVR Working Group";
  
  contact
    "WG Web:   <https://datatracker.ietf.org/wg/lsvr>
     WG List:  <lsvr@ietf.org>

     Authors: Mahesh Jethanandani (mjethanandani at gmail.com),
              Keyur Patel (keyur at arrcus.com)";

  description
    "This submodule contains groupings for OSPFv2/OSPFv3
     node and link NLRIs.
    
     Copyright (c) 2025 IETF Trust and the persons identified as
     authors of the code. All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";

  revision YYYY-MM-DD {
    description
      "Initial Version";
    reference
      "RFC XXXX, BGP Model for Link State Distribution.";
  }

  grouping bgp-ls-ospf-node-common {
    description
      "Common fields for OSPFv2 and OSPFv3 node NLRIs.";

    leaf is-as-scoped {
      type boolean;
      description
        "When true, the NLRI is AS-scoped and the area-id
         is not applicable.";
    }

    leaf area-id {
      type ietf-ospf-t:area-id-type;
      description
        "Area ID.";
      reference
        "RFC 9552: Distribution of Link-State and Traffic
         Engineering Information Using BGP,
         Section 5.2.1. TLV 514.";
    }

    leaf router-id {
      type ietf-rt-t:router-id;
      description
        "Router ID.";
      reference
        "RFC 9552: Distribution of Link-State and Traffic
         Engineering Information Using BGP,
         Section 5.2.1. TLV 515.";
    }

    leaf dr-identifier {
      type union {
        type inet:ipv4-address;
        type uint32;
      }
      description
        "Designated Router (DR) Identifier.";
      reference
        "RFC 9552: Distribution of Link-State and Traffic
         Engineering Information Using BGP,
         Section 5.2.1. TLV 515.";
    }

    leaf as {
      type inet:as-number;
      description
        "Autonomous System (AS) number associated with the
         BGP process originating the NLRI.";
      reference
        "RFC 9552: Distribution of Link-State and Traffic
         Engineering Information Using BGP,
         Section 5.2.1. TLV 512.";
    }
  }

  grouping bgp-ls-ospf-link-common {
    description
      "Common fields for OSPFv2 and OSPFv3 link NLRIs.";

    leaf area-id {
      type ietf-ospf-t:area-id-type;
      description
        "Area ID.";
      reference
        "RFC 9552: Distribution of Link-State and Traffic
         Engineering Information Using BGP,
         Section 5.2.1. TLV 514.";
    }

    leaf as {
      type inet:as-number;
      description
        "Autonomous System (AS) number associated with the
         BGP process originating the NLRI.";
      reference
        "RFC 9552: Distribution of Link-State and Traffic
         Engineering Information Using BGP,
         Section 5.2.1. TLV 512.";
    }

    leaf local-router-id {
      type ietf-rt-t:router-id;
      description
        "Local Router ID.";
      reference
        "RFC 9552: Distribution of Link-State and Traffic
         Engineering Information Using BGP,
         Section 5.2.1. TLV 515.";
    }

    leaf remote-router-id {
      type ietf-rt-t:router-id;
      description
        "Remote Router ID.";
      reference
        "RFC 9552: Distribution of Link-State and Traffic
         Engineering Information Using BGP,
         Section 5.2.1. TLV 515.";
    }

    leaf local-id {
      type uint32;
      description
        "Local Identifier of a link.";
      reference
        "RFC 9552: Distribution of Link-State and Traffic
         Engineering Information Using BGP,
         Section 5.2.2. TLV 258.";
    }

    leaf remote-id {
      type uint32;
      description
        "Remote Identifier of a link.";
      reference
        "RFC 9552: Distribution of Link-State and Traffic
         Engineering Information Using BGP,
         Section 5.2.2. TLV 258.";
    }

    leaf local-ipv4-address {
      type inet:ipv4-address;
      description
        "Local IPv4 address of a link. Use 0.0.0.0 as a sentinel
         value when this address is not present (e.g., for
         unnumbered or IPv6-only links).";
      reference
        "RFC 9552: Distribution of Link-State and Traffic
         Engineering Information Using BGP,
         Section 5.2.2. TLV 259.";
    }

    leaf remote-ipv4-address {
      type inet:ipv4-address;
      description
        "Remote IPv4 address of a link. Use 0.0.0.0 as a sentinel
         value when this address is not present (e.g., for
         unnumbered or IPv6-only links).";
      reference
        "RFC 9552: Distribution of Link-State and Traffic
         Engineering Information Using BGP,
         Section 5.2.2. TLV 260.";
    }

    leaf multi-topology-id {
      type uint16;
      description
        "Multi Topology Identifier (MTID) of a link.";
      reference
        "RFC 9552: Distribution of Link-State and Traffic
         Engineering Information Using BGP,
         Section 5.2.2.1. TLV 263.";
    }
  }

  grouping bgp-ls-ospf-prefix-common {
    description
      "Common fields for OSPFv2 and OSPFv3 prefix NLRIs.";

    leaf is-as-scoped {
      type boolean;
      description
        "When true, the NLRI is AS-scoped and the area-id
         is not applicable.";
    }

    leaf area-id {
      type ietf-ospf-t:area-id-type;
      description
        "Area ID.";
      reference
        "RFC 9552: Distribution of Link-State and Traffic
         Engineering Information Using BGP,
         Section 5.2.1. TLV 514.";
    }

    leaf as {
      type inet:as-number;
      description
        "Autonomous System (AS) number associated with the
         BGP process originating the NLRI.";
      reference
        "RFC 9552: Distribution of Link-State and Traffic
         Engineering Information Using BGP,
         Section 5.2. TLV 512.";
    }

    leaf router-id {
      type ietf-rt-t:router-id;
      description
        "Router ID.";
      reference
        "RFC 9552: Distribution of Link-State and Traffic
         Engineering Information Using BGP,
         Section 5.2.1. TLV 515.";
    }

    leaf route-type {
      type bgp-ls-topo-t:ospf-route-type;
      description
        "OSPF Route type of a prefix.";
      reference
        "RFC 9552: Distribution of Link-State and Traffic
         Engineering Information Using BGP,
         Section 5.2.3.1. TLV 264.";
    }

    leaf multi-topology-id {
      type uint16;
      description
        "Multi Topology Identifier (MTID) of a prefix.";
      reference
        "RFC 9552: Distribution of Link-State and Traffic
         Engineering Information Using BGP,
         Section 5.2.2.1. TLV 263.";
    }

  }
}
